FME workspace Ftransformasjon og formater.fmw

Parameters:
- SourceDataset_SOSI_GML = ""$(FME_MF_DIR)Nedlastingspakke\Basisdata_5972_FKB-Arealbruk_GML.gml" "$(FME_MF_DIR)Nedlastingspakke\Basisdata_5972_FKB-Bane_GML.gml" "$(FME_MF_DIR)Nedlastingspakke\Basisdata_5972_FKB-BygnAnlegg_GML.gml" "$(FME_MF_DIR)Nedlastingspakke\Basisdata_5972_FKB-Bygning_GML.gml" "$(FME_MF_DIR)Nedlastingspakke\Basisdata_5972_FKB-Ledning_GML.gml" "$(FME_MF_DIR)Nedlastingspakke\Basisdata_5972_FKB-Tiltak_GML.gml" "$(FME_MF_DIR)Nedlastingspakke\Basisdata_5972_FKB-TraktorvegSti_GML.gml" "$(FME_MF_DIR)Nedlastingspakke\Basisdata_5972_FKB-Vann_GML.gml" "$(FME_MF_DIR)Nedlastingspakke\Basisdata_5972_FKB-Veg_GML.gml""   # Source SOSI GML File(s)
- FEATURE_TYPES =
- DestDataset_SOSI_GML = $(FME_MF_DIR)NTM10\FKBNTM10.gml   # Destination Geography Markup Language (GML) File
- DestDataset_REALDWG = $(FME_MF_DIR)NTM10\FKBNTM10.dwg   # Destination Autodesk AutoCAD RealDWG File
- DestDataset_IFC = $(FME_MF_DIR)NTM10\FKBNTM10.ifc   # Destination Industry Foundation Class (IFC) File(s)
- SourceDataset_GDMMAPPERSOSI = ""$(FME_MF_DIR)Nedlastingspakke\Basisdata_5972_FKB-Arealbruk_SOSI.sos" "$(FME_MF_DIR)Nedlastingspakke\Basisdata_5972_FKB-Bane_SOSI.sos" "$(FME_MF_DIR)Nedlastingspakke\Basisdata_5972_FKB-BygnAnlegg_SOSI.sos" "$(FME_MF_DIR)Nedlastingspakke\Basisdata_5972_FKB-Bygning_SOSI.sos" "$(FME_MF_DIR)Nedlastingspakke\Basisdata_5972_FKB-Ledning_SOSI.sos" "$(FME_MF_DIR)Nedlastingspakke\Basisdata_5972_FKB-Tiltak_SOSI.sos" "$(FME_MF_DIR)Nedlastingspakke\Basisdata_5972_FKB-TraktorvegSti_SOSI.sos" "$(FME_MF_DIR)Nedlastingspakke\Basisdata_5972_FKB-Vann_SOSI.sos" "$(FME_MF_DIR)Nedlastingspakke\Basisdata_5972_FKB-Veg_SOSI.sos""   # Source GDM File
- DestDataset_GDMMAPPERSOSI = $(FME_MF_DIR)NTM10\FKBNTM10.sos   # SOSI_Files(*.sos) Destination SOSI 

Readers:
- SOSI_GML_1: SOSI_GML from $(SourceDataset_SOSI_GML)
- GDMMAPPERSOSI_1: GDMMAPPERSOSI from $(SourceDataset_GDMMAPPERSOSI)

Writers:
- SOSI_GML_2: SOSI_GML to $(DestDataset_SOSI_GML)
- REALDWG_1: REALDWG to $(DestDataset_REALDWG)
- IFC_1: IFC to $(DestDataset_IFC)
- GDMMAPPERSOSI_2: GDMMAPPERSOSI to $(DestDataset_GDMMAPPERSOSI)

NTM10: Reprojector
    DEST = EUREF89.NTM-10
    INTERPOLATION_TYPE_NAME = Nearest Neighbor
    RASTER_CELL_SIZE = Preserve Cells
    RASTER_TOLERANCE = 0.0
    SOURCE = Read from feature
    REPROJECTED -> DYNAMIC (writer SOSI_GML_2)
    REPROJECTED -> LayeræøÅ123456789 (writer REALDWG_1)
    REPROJECTED -> AttributeCreator
NTM10_2: Reprojector
    DEST = EUREF89.NTM-10
    INTERPOLATION_TYPE_NAME = Nearest Neighbor
    RASTER_CELL_SIZE = Preserve Cells
    RASTER_TOLERANCE = 0.0
    SOURCE = Read from feature
    REPROJECTED -> DYNAMIC (writer GDMMAPPERSOSI_2)

Bookmark: FKB GML UTM32
AnnetVegarealAvgrensning (reader SOSI_GML_1)
    attributes: gml_metaDataProperty{}.about xml_buffer, gml_metaDataProperty{}.nilReason xml_buffer, gml_metaDataProperty{}.gml_remoteSchema xml_buffer, gml_metaDataProperty{}.xlink_href xml_buffer, gml_metaDataProperty{}.xlink_role xml_buffer, gml_metaDataProperty{}.xlink_title xml_buffer, gml_metaDataProperty{}.gml_GenericMetaData xml_xml, gml_metaDataProperty{}.gml_GenericMetaData.gml_id xml_buffer, gml_description xml_buffer, gml_description.nilReason xml_buffer, gml_description.gml_remoteSchema xml_buffer, gml_description.xlink_href xml_buffer, gml_description.xlink_role xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_role xml_buffer, gml_descriptionReference.xlink_title xml_buffer, gml_identifier xml_buffer, gml_identifier.codeSpace xml_buffer, gml_name{} xml_buffer, gml_name{}.codeSpace xml_buffer, gml_boundedBy xml_geometry, gml_priorityLocation xml_geometry, gml_location xml_geometry, identifikasjon.Identifikasjon.lokalId xml_buffer, identifikasjon.Identifikasjon.navnerom xml_buffer, identifikasjon.Identifikasjon.versjonId xml_buffer,
      datafangstdato xml_date, registreringsversjon.Registreringsversjon.produkt xml_buffer, registreringsversjon.Registreringsversjon.versjon xml_buffer, registreringsversjon.Registreringsversjon.undertype xml_buffer, verifiseringsdato xml_date, oppdateringsdato xml_datetime, informasjon xml_buffer, prosesshistorie xml_buffer, kopidata.Kopidata.områdeId xml_int64, kopidata.Kopidata.originalDatavert xml_buffer, kopidata.Kopidata.kopidato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, grense xml_geometry, medium xml_buffer, senterlinje xml_geometry, vegreferanse.Vegreferanse.vegstatus xml_buffer, område xml_geometry, vegreferanse.Vegreferanse.vegkategori xml_buffer, posisjon xml_geometry, vegbomtype xml_buffer, høydereferanse xml_buffer, kant xml_geometry, nedsenketKantstein xml_boolean, vegreferanse.Vegreferanse.vegnummer xml_int64, vegOverVeg xml_boolean, rekkverkstype xml_buffer
    -> NTM10

Bookmark: FKB GML
DYNAMIC (writer SOSI_GML_2)

Bookmark: FKB DWG
LayeræøÅ123456789 (writer REALDWG_1)

Bookmark: FKB IFC
AttributeCreator
    ATTR_TABLE:
      SET_TO Name = @Value(fme_feature_type)
      SET_TO LongName = @Value(fme_feature_type)
    -> GeometryPropertySetter_4
GeometryPropertySetter_4
    OVERWRITE_CHOICE = Yes
    REMOVE_ATTRIBUTE = No
    SETTYPE_PARAM = Traits From Attributes
    SRC_ATTRS = fme_feature_type Name datafangstdato prosesshistorie gml_identifier informasjon medium
    SET -> GeometryPropertySetter
GeometryPropertySetter
    GEOM_NAME_FIELD = Body
    GQUERY:
      for $geom in //geometry
      where $geom/count(parent::geometry) = 0
      return number($geom/@fme_id)
    OVERWRITE_CHOICE = Yes
    SETTYPE_PARAM = Geometry Name
    SET -> IfcSpace (writer IFC_1)
IfcSpace (writer IFC_1)

Bookmark: FKB SOSI UTM32
Anleggsområde (reader GDMMAPPERSOSI_1)
    attributes: DATAFANGSTDATO number(9,0), KOPIDATA.ORIGINALDATAVERT char(11), OBJTYPE char(14), KOPIDATA.OMRÅDEID number(5,0), IDENT.LOKALID char(37), OPPDATERINGSDATO number(15,0), IDENT.VERSJONID char(27), IDENT.NAVNEROM char(46), KOPIDATA.KOPIDATO number(15,0), REGISTRERINGSVERSJON.PRODUKT char(4), REGISTRERINGSVERSJON.VERSJON number(3,1), HREF char(4), INFORMASJON char(37), VREF.NVDB_VEGKATEGORI char(2), TRE_D_NIVÅ number(2,0), KVALITET.MÅLEMETODE number(3,0), KVALITET.H-MÅLEMETODE number(3,0), SAKSNR number(7,0), SEFRAKIDENT{}.SEFRAKIDENT.HUSLØPENUMMER number(9,0), RUTEMERKING char(3), TRANSPAR.VERT-DATUM.HØYDE-REF char(7), TRANSPAR.ENHET number(5,3), BELYSNINGSPLASSERING char(6), OBJEKTKATALOG.KORTNAVN char(255), MASTEKONSTRUKSJON number(2,0), VREF.NVDB_VEGSTATUS char(2), PBTILTAK number(3,0), BYGGTYP_NBR number(4,0), BYGGSTAT char(3), VERIFISERINGSDATO number(9,0),
      KUMFUNKSJON char(10), SOSI-VERSJON number(3,1), LEDN_HØYDEREFERANSE char(13), KVALITET.H-NØYAKTIGHET number(4,0), BELYSNING number(2,0), KARTREG number(2,0), LEDN_EIER{}.LEDN_EIER.LEDN_EIERTYPE number(9,0), HØYDE number(7,3), LEDN_EIER{}.LEDN_EIER.LEDN_EIERNAVN number(9,0), TILTAKNR number(2,0), KOMM number(5,0), KVALITET.NØYAKTIGHET number(4,0), SOSI-NIVÅ number(2,0), TYPEVEG char(11), SEFRAKIDENT{}.SEFRAKIDENT.KOMM number(9,0), VEDTAK number(2,0), VANNBR number(2,0), BELYSNINGSBRUK number(2,0), JERNBANETYPE char(2), BYGN_ENDR_LØPENR number(2,0), BYGGNR number(10,0), PROSESS_HISTORIE char(109), AVGJDATO number(9,0), REGMETOD number(2,0), VREF.VEGNUMMER number(6,0), MEDIUM char(2), OBJEKTKATALOG.VERSJON char(255), KVALITET.SYNBARHET number(2,0), SEFRAKIDENT{}.SEFRAKIDENT.REGISTRERINGSKRETSNUMMER number(9,0), TRANSPAR.KOORDSYS number(3,0),
      LEDNINGSNETTVERKSTYPE char(13), MASTEFUNKSJON char(20), TEGNSETT char(6), EL_STASJONSTYPE char(17)
    -> NTM10_2

Bookmark: FKB SOSI
DYNAMIC (writer GDMMAPPERSOSI_2)
